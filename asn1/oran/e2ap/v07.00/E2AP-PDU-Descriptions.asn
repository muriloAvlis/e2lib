-- ASN1START
-- **************************************************************
--
-- Elementary Procedure definitions
-- Derived from 3GPP 38.413 NGAP
-- **************************************************************
E2AP-PDU-Descriptions {iso (1) identified-organization (3) dod (6) internet (1) private (4) enterprise (1) 53148 e2 (1) version2 (2) e2ap (1) e2ap-PDU-Descriptions (0)}
DEFINITIONS AUTOMATIC TAGS ::= BEGIN

-- **************************************************************
--
-- IE parameter types from other modules.
--
-- **************************************************************

IMPORTS
     Criticality, ProcedureCode
          FROM E2AP-CommonDataTypes
     E2connectionUpdate, E2connectionUpdateAcknowledge, E2connectionUpdateFailure, E2nodeConfigurationUpdate, E2nodeConfigurationUpdateAcknowledge, E2nodeConfigurationUpdateFailure, E2RemovalRequest, E2RemovalResponse, E2RemovalFailure, E2setupFailure, E2setupRequest, E2setupResponse, ErrorIndication, ResetRequest,
     ResetResponse, RICassistanceFailure, RICassistanceIndication, RICassistanceHalt, RICassistanceRequest, RICassistanceResponse, RICcontrolAcknowledge, RICcontrolFailure, RICcontrolRequest, RICindication, RICserviceLoadStatusRequest, RICserviceLoadStatusResponse, RICserviceLoadStatusFailure, RICserviceLoadUpdate,
     RICserviceQuery, RICserviceUpdate, RICserviceUpdateAcknowledge, RICserviceUpdateFailure, RICsubscriptionFailure, RICsubscriptionRequest, RICsubscriptionResponse, RICsubscriptionAuditFailure, RICsubscriptionAuditRequest, RICsubscriptionAuditResponse, RICsubscriptionDeleteFailure, RICsubscriptionDeleteRequest,
     RICsubscriptionDeleteResponse, RICsubscriptionDeleteRequired, RICsubscriptionModificationRequest, RICsubscriptionModificationResponse, RICsubscriptionModificationFailure, RICsubscriptionModificationRequired, RICsubscriptionModificationConfirm, RICsubscriptionModificationRefuse, RICsubscriptionStateControlRequest,
     RICsubscriptionStateControlResponse, RICsubscriptionStateControlFailure, RICqueryRequest, RICqueryResponse, RICqueryFailure
          FROM E2AP-PDU-Contents
     id-E2connectionUpdate, id-E2nodeConfigurationUpdate, id-E2removal, id-E2setup, id-ErrorIndication, id-Reset, id-RICassistance, id-RICassistanceIndication, id-RICassistanceHalt, id-RICcontrol, id-RICindication, id-RICserviceLoadStatus, id-RICserviceLoadUpdate, id-RICserviceQuery, id-RICserviceUpdate, id-RICsubscription,
     id-RICsubscriptionAudit, id-RICsubscriptionDelete, id-RICsubscriptionDeleteRequired, id-RICsubscriptionModification, id-RICsubscriptionModificationRequired, id-RICsubscriptionStateControl, id-RICquery
          FROM E2AP-Constants;

-- **************************************************************
--
-- Interface Elementary Procedure Class
--
-- **************************************************************
E2AP-ELEMENTARY-PROCEDURE ::= CLASS {
    &InitiatingMessage,
    &SuccessfulOutcome OPTIONAL,
    &UnsuccessfulOutcome OPTIONAL,
    &procedureCode ProcedureCode UNIQUE,
    &criticality   Criticality DEFAULT ignore
}
WITH SYNTAX {
    INITIATING MESSAGE &InitiatingMessage [SUCCESSFUL OUTCOME &SuccessfulOutcome] [UNSUCCESSFUL OUTCOME &UnsuccessfulOutcome] PROCEDURE CODE &procedureCode [CRITICALITY &criticality]
}

-- **************************************************************
--
-- Interface PDU Definition
--
-- **************************************************************
E2AP-PDU ::= CHOICE {
    initiatingMessage InitiatingMessage,
    successfulOutcome SuccessfulOutcome,
    unsuccessfulOutcome UnsuccessfulOutcome,
    ...
}

InitiatingMessage ::= SEQUENCE {
    procedureCode  E2AP-ELEMENTARY-PROCEDURE.&procedureCode ({E2AP-ELEMENTARY-PROCEDURES}),
    criticality    E2AP-ELEMENTARY-PROCEDURE.&criticality ({E2AP-ELEMENTARY-PROCEDURES} {@procedureCode}),
    value          E2AP-ELEMENTARY-PROCEDURE.&InitiatingMessage ({E2AP-ELEMENTARY-PROCEDURES} {@procedureCode})
}

SuccessfulOutcome ::= SEQUENCE {
    procedureCode  E2AP-ELEMENTARY-PROCEDURE.&procedureCode ({E2AP-ELEMENTARY-PROCEDURES}),
    criticality    E2AP-ELEMENTARY-PROCEDURE.&criticality ({E2AP-ELEMENTARY-PROCEDURES} {@procedureCode}),
    value          E2AP-ELEMENTARY-PROCEDURE.&SuccessfulOutcome ({E2AP-ELEMENTARY-PROCEDURES} {@procedureCode})
}

UnsuccessfulOutcome ::= SEQUENCE {
    procedureCode  E2AP-ELEMENTARY-PROCEDURE.&procedureCode ({E2AP-ELEMENTARY-PROCEDURES}),
    criticality    E2AP-ELEMENTARY-PROCEDURE.&criticality ({E2AP-ELEMENTARY-PROCEDURES} {@procedureCode}),
    value          E2AP-ELEMENTARY-PROCEDURE.&UnsuccessfulOutcome ({E2AP-ELEMENTARY-PROCEDURES} {@procedureCode})
}

-- **************************************************************
--
-- Interface Elementary Procedure List
--
-- **************************************************************
E2AP-ELEMENTARY-PROCEDURES E2AP-ELEMENTARY-PROCEDURE ::= {
    E2AP-ELEMENTARY-PROCEDURES-CLASS-1 |
    E2AP-ELEMENTARY-PROCEDURES-CLASS-2,
    ...
}

E2AP-ELEMENTARY-PROCEDURES-CLASS-1 E2AP-ELEMENTARY-PROCEDURE ::= {
    ricSubscription |
    ricSubscriptionAudit |
    ricSubscriptionDelete |
    ricSubscriptionModification |
    ricSubscriptionModificationRequired |
    ricSubscriptionStateControl |
    ricQuery |
    ricServiceUpdate |
    ricAssistance |
    ricControl |
    ricServiceLoadStatus |
    e2setup |
    e2nodeConfigurationUpdate |
    e2connectionUpdate |
    reset |
    e2removal,
    ...
}

E2AP-ELEMENTARY-PROCEDURES-CLASS-2 E2AP-ELEMENTARY-PROCEDURE ::= {
    ricAssistanceIndication |
    ricAssistanceHalt |
    ricIndication |
    ricServiceQuery |
    ricServiceLoadUpdate |
    errorIndication |
    ricSubscriptionDeleteRequired,
    ...
}

-- **************************************************************
--
-- Interface Elementary Procedures
--
-- **************************************************************
-- New for v01.01
e2connectionUpdate E2AP-ELEMENTARY-PROCEDURE ::= {INITIATING MESSAGE E2connectionUpdate SUCCESSFUL OUTCOME E2connectionUpdateAcknowledge UNSUCCESSFUL OUTCOME E2connectionUpdateFailure PROCEDURE CODE id-E2connectionUpdate CRITICALITY reject}

e2nodeConfigurationUpdate E2AP-ELEMENTARY-PROCEDURE ::= {INITIATING MESSAGE E2nodeConfigurationUpdate SUCCESSFUL OUTCOME E2nodeConfigurationUpdateAcknowledge UNSUCCESSFUL OUTCOME E2nodeConfigurationUpdateFailure PROCEDURE CODE id-E2nodeConfigurationUpdate CRITICALITY reject}

-- New for v02.01
e2removal      E2AP-ELEMENTARY-PROCEDURE ::= {INITIATING MESSAGE E2RemovalRequest SUCCESSFUL OUTCOME E2RemovalResponse UNSUCCESSFUL OUTCOME E2RemovalFailure PROCEDURE CODE id-E2removal CRITICALITY reject}

e2setup        E2AP-ELEMENTARY-PROCEDURE ::= {INITIATING MESSAGE E2setupRequest SUCCESSFUL OUTCOME E2setupResponse UNSUCCESSFUL OUTCOME E2setupFailure PROCEDURE CODE id-E2setup CRITICALITY reject}

errorIndication E2AP-ELEMENTARY-PROCEDURE ::= {INITIATING MESSAGE ErrorIndication PROCEDURE CODE id-ErrorIndication CRITICALITY ignore}

reset          E2AP-ELEMENTARY-PROCEDURE ::= {INITIATING MESSAGE ResetRequest SUCCESSFUL OUTCOME ResetResponse PROCEDURE CODE id-Reset CRITICALITY reject}

ricAssistance  E2AP-ELEMENTARY-PROCEDURE ::= {INITIATING MESSAGE RICassistanceRequest SUCCESSFUL OUTCOME RICassistanceResponse UNSUCCESSFUL OUTCOME RICassistanceFailure PROCEDURE CODE id-RICassistance CRITICALITY reject}

ricAssistanceIndication E2AP-ELEMENTARY-PROCEDURE ::= {INITIATING MESSAGE RICassistanceIndication PROCEDURE CODE id-RICassistanceIndication CRITICALITY reject}

ricAssistanceHalt E2AP-ELEMENTARY-PROCEDURE ::= {INITIATING MESSAGE RICassistanceHalt PROCEDURE CODE id-RICassistanceHalt CRITICALITY reject}

ricControl     E2AP-ELEMENTARY-PROCEDURE ::= {INITIATING MESSAGE RICcontrolRequest SUCCESSFUL OUTCOME RICcontrolAcknowledge UNSUCCESSFUL OUTCOME RICcontrolFailure PROCEDURE CODE id-RICcontrol CRITICALITY reject}

ricIndication  E2AP-ELEMENTARY-PROCEDURE ::= {INITIATING MESSAGE RICindication PROCEDURE CODE id-RICindication CRITICALITY ignore}

ricServiceLoadStatus E2AP-ELEMENTARY-PROCEDURE ::= {INITIATING MESSAGE RICserviceLoadStatusRequest SUCCESSFUL OUTCOME RICserviceLoadStatusResponse UNSUCCESSFUL OUTCOME RICserviceLoadStatusFailure PROCEDURE CODE id-RICserviceLoadStatus CRITICALITY ignore}

ricServiceLoadUpdate E2AP-ELEMENTARY-PROCEDURE ::= {INITIATING MESSAGE RICserviceLoadUpdate PROCEDURE CODE id-RICserviceLoadUpdate CRITICALITY ignore}

ricServiceQuery E2AP-ELEMENTARY-PROCEDURE ::= {INITIATING MESSAGE RICserviceQuery PROCEDURE CODE id-RICserviceQuery CRITICALITY ignore}

ricServiceUpdate E2AP-ELEMENTARY-PROCEDURE ::= {INITIATING MESSAGE RICserviceUpdate SUCCESSFUL OUTCOME RICserviceUpdateAcknowledge UNSUCCESSFUL OUTCOME RICserviceUpdateFailure PROCEDURE CODE id-RICserviceUpdate CRITICALITY reject}

ricSubscription E2AP-ELEMENTARY-PROCEDURE ::= {INITIATING MESSAGE RICsubscriptionRequest SUCCESSFUL OUTCOME RICsubscriptionResponse UNSUCCESSFUL OUTCOME RICsubscriptionFailure PROCEDURE CODE id-RICsubscription CRITICALITY reject}

ricSubscriptionAudit E2AP-ELEMENTARY-PROCEDURE ::= {INITIATING MESSAGE RICsubscriptionAuditRequest SUCCESSFUL OUTCOME RICsubscriptionAuditResponse UNSUCCESSFUL OUTCOME RICsubscriptionAuditFailure PROCEDURE CODE id-RICsubscriptionAudit CRITICALITY reject}

ricSubscriptionDelete E2AP-ELEMENTARY-PROCEDURE ::= {INITIATING MESSAGE RICsubscriptionDeleteRequest SUCCESSFUL OUTCOME RICsubscriptionDeleteResponse UNSUCCESSFUL OUTCOME RICsubscriptionDeleteFailure PROCEDURE CODE id-RICsubscriptionDelete CRITICALITY reject}

ricSubscriptionDeleteRequired E2AP-ELEMENTARY-PROCEDURE ::= {INITIATING MESSAGE RICsubscriptionDeleteRequired PROCEDURE CODE id-RICsubscriptionDeleteRequired CRITICALITY ignore}

ricSubscriptionModification E2AP-ELEMENTARY-PROCEDURE ::= {INITIATING MESSAGE RICsubscriptionModificationRequest SUCCESSFUL OUTCOME RICsubscriptionModificationResponse UNSUCCESSFUL OUTCOME RICsubscriptionModificationFailure PROCEDURE CODE id-RICsubscriptionModification CRITICALITY reject}

ricSubscriptionModificationRequired E2AP-ELEMENTARY-PROCEDURE ::= {INITIATING MESSAGE RICsubscriptionModificationRequired SUCCESSFUL OUTCOME RICsubscriptionModificationConfirm UNSUCCESSFUL OUTCOME RICsubscriptionModificationRefuse PROCEDURE CODE id-RICsubscriptionModificationRequired CRITICALITY reject}

ricSubscriptionStateControl E2AP-ELEMENTARY-PROCEDURE ::= {INITIATING MESSAGE RICsubscriptionStateControlRequest SUCCESSFUL OUTCOME RICsubscriptionStateControlResponse UNSUCCESSFUL OUTCOME RICsubscriptionStateControlFailure PROCEDURE CODE id-RICsubscriptionStateControl CRITICALITY reject}

ricQuery       E2AP-ELEMENTARY-PROCEDURE ::= {INITIATING MESSAGE RICqueryRequest SUCCESSFUL OUTCOME RICqueryResponse UNSUCCESSFUL OUTCOME RICqueryFailure PROCEDURE CODE id-RICquery CRITICALITY reject}

END

     -- ASN1STOP
