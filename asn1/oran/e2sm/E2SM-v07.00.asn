-- ASN1START
-- **************************************************************
-- E2SM
-- Information Element Definitions
--
-- **************************************************************
E2SM-COMMON-IEs {iso (1) identified-organization (3) dod (6) internet (1) private (4) enterprise (1) 53148 e2 (1) version1 (1) e2sm (2) e2sm-COMMON-IEs (0)}
DEFINITIONS AUTOMATIC TAGS ::= BEGIN

-- --------------------------------------------------
-- Constants
-- --------------------------------------------------
maxE1APid      INTEGER ::= 65535

maxF1APid      INTEGER ::= 4

-- IEs derived from 3GPP 36.423 (X2AP)
maxEARFCN      INTEGER ::= 65535

-- IEs derived from 3GPP 38.473 (F1AP)
maxNRARFCN     INTEGER ::= 3279165

maxnoofNrCellBands INTEGER ::= 32

-- IEs derived from 3GPP 38.331 (NR RRC)
maxNrofSSBs-1  INTEGER ::= 63

-- --------------------------------------------------
-- E2SM Common IEs
-- --------------------------------------------------
Beam-ID ::= CHOICE {
    nR-Beam-ID     NR-SSB-Index,
    ...
}

Cell-RNTI ::= SEQUENCE {
    c-RNTI         RNTI-Value,
    cell-Global-ID CGI,
    ...
}

CGI ::= CHOICE {
    nR-CGI         NR-CGI,
    eUTRA-CGI      EUTRA-CGI,
    ...
}

CoreCPID ::= CHOICE {
    fiveGC         GUAMI,
    ePC            GUMMEI,
    ...
}

InterfaceIdentifier ::= CHOICE {
    nG             InterfaceID-NG,
    xN             InterfaceID-Xn,
    f1             InterfaceID-F1,
    e1             InterfaceID-E1,
    s1             InterfaceID-S1,
    x2             InterfaceID-X2,
    w1             InterfaceID-W1,
    ...
}

InterfaceID-NG ::= SEQUENCE {
    guami          GUAMI,
    ...
}

InterfaceID-Xn ::= SEQUENCE {
    global-NG-RAN-ID GlobalNGRANNodeID,
    ...
}

InterfaceID-F1 ::= SEQUENCE {
    globalGNB-ID   GlobalGNB-ID,
    gNB-DU-ID      GNB-DU-ID,
    ...
}

InterfaceID-E1 ::= SEQUENCE {
    globalGNB-ID   GlobalGNB-ID,
    gNB-CU-UP-ID   GNB-CU-UP-ID,
    ...
}

InterfaceID-S1 ::= SEQUENCE {
    gUMMEI         GUMMEI,
    ...
}

InterfaceID-X2 ::= SEQUENCE {
    nodeType       CHOICE {
        global-eNB-ID  GlobalENB-ID,
        global-en-gNB-ID GlobalenGNB-ID,
        ...
    },
    ...
}

InterfaceID-W1 ::= SEQUENCE {
    global-ng-eNB-ID GlobalNgENB-ID,
    ng-eNB-DU-ID   NGENB-DU-ID,
    ...
}

Interface-MessageID ::= SEQUENCE {
    interfaceProcedureID INTEGER,
    messageType    ENUMERATED {
                       initiatingMessage,
                       successfulOutcome,
                       unsuccessfulOutcome,
                       ...
                   },
    ...
}

InterfaceType ::= ENUMERATED {
                   nG,
                   xn,
                   f1,
                   e1,
                   s1,
                   x2,
                   w1,
                   ...
               }

GroupID ::= CHOICE {
    fiveGC         FiveQI,
    ePC            QCI,
    ...
}

PartialUEID ::= SEQUENCE {
    amf-UE-NGAP-ID AMF-UE-NGAP-ID OPTIONAL,
    guami          GUAMI OPTIONAL,
    gNB-CU-UE-F1AP-ID GNB-CU-UE-F1AP-ID OPTIONAL,
    gNB-CU-CP-UE-E1AP-ID GNB-CU-CP-UE-E1AP-ID OPTIONAL,
    ran-UEID       RANUEID OPTIONAL,
    m-NG-RAN-UE-XnAP-ID NG-RANnodeUEXnAPID OPTIONAL,
    globalNG-RANNode-ID GlobalNGRANNodeID OPTIONAL,
    cell-RNTI      Cell-RNTI OPTIONAL,
    ng-eNB-CU-UE-W1AP-ID NGENB-CU-UE-W1AP-ID OPTIONAL,
    m-eNB-UE-X2AP-ID ENB-UE-X2AP-ID OPTIONAL,
    m-eNB-UE-X2AP-ID-Extension ENB-UE-X2AP-ID-Extension OPTIONAL,
    globalENB-ID   GlobalENB-ID OPTIONAL,
    mME-UE-S1AP-ID MME-UE-S1AP-ID OPTIONAL,
    gUMMEI         GUMMEI OPTIONAL,
    ...
}

QoSID ::= CHOICE {
    fiveGC         FiveQI,
    ePC            QCI,
    ...
}

RANfunction-Name ::= SEQUENCE {
    ranFunction-ShortName PrintableString (SIZE (1..150, ...)),
    ranFunction-E2SM-OID PrintableString (SIZE (1..1000, ...)),
    ranFunction-Description PrintableString (SIZE (1..150, ...)),
    ranFunction-Instance INTEGER OPTIONAL,
    ...
}

RIC-Format-Type ::= INTEGER

RIC-Style-Type ::= INTEGER

RIC-Style-Name ::= PrintableString (SIZE (1..150, ...))

RRC-MessageID ::= SEQUENCE {
    rrcType        CHOICE {
        lTE            RRCclass-LTE,
        nR             RRCclass-NR,
        ...
    },
    messageID      INTEGER,
    ...
}

RRCclass-LTE ::= ENUMERATED {
                   bCCH-BCH,
                   bCCH-BCH-MBMS,
                   bCCH-DL-SCH,
                   bCCH-DL-SCH-BR,
                   bCCH-DL-SCH-MBMS,
                   mCCH,
                   pCCH,
                   dL-CCCH,
                   dL-DCCH,
                   uL-CCCH,
                   uL-DCCH,
                   sC-MCCH,
                   ...
               }

RRCclass-NR ::= ENUMERATED {
                   bCCH-BCH,
                   bCCH-DL-SCH,
                   dL-CCCH,
                   dL-DCCH,
                   pCCH,
                   uL-CCCH,
                   uL-CCCH1,
                   uL-DCCH,
                   ...
               }

ServingCell-ARFCN ::= CHOICE {
    nR             NR-ARFCN,
    eUTRA          E-UTRA-ARFCN,
    ...
}

ServingCell-PCI ::= CHOICE {
    nR             NR-PCI,
    eUTRA          E-UTRA-PCI,
    ...
}

UEID ::= CHOICE {
    gNB-UEID       UEID-GNB,
    gNB-DU-UEID    UEID-GNB-DU,
    gNB-CU-UP-UEID UEID-GNB-CU-UP,
    ng-eNB-UEID    UEID-NG-ENB,
    ng-eNB-DU-UEID UEID-NG-ENB-DU,
    en-gNB-UEID    UEID-EN-GNB,
    eNB-UEID       UEID-ENB,
    ...
}

UEID-GNB ::= SEQUENCE {
    amf-UE-NGAP-ID AMF-UE-NGAP-ID,
    guami          GUAMI,
    gNB-CU-UE-F1AP-ID-List UEID-GNB-CU-F1AP-ID-List OPTIONAL,
    -- C-ifCUDUseparated: This IE shall be present in messages from E2 Node to NearRT-RIC for a CU-DU separated gNB, whereas from NearRT-RIC to E2 Node messages, this IE may not be included. More than 1 F1AP ID shall be reported by E2 Node only when NR-DC is established.
    gNB-CU-CP-UE-E1AP-ID-List UEID-GNB-CU-CP-E1AP-ID-List OPTIONAL,
    -- C-ifCPUPseparated: This IE shall be present in messages from E2 Node to NearRT-RIC for a CP-UP separated gNB, whereas from NearRT-RIC to E2 Node messages, this IE may not be included.
    ran-UEID       RANUEID OPTIONAL,
    m-NG-RAN-UE-XnAP-ID NG-RANnodeUEXnAPID OPTIONAL,
    -- C-ifDCSetup: This IE shall be present in messages from E2 Node to NearRT-RIC if DC is established, whereas from NearRT-RIC to E2 Node messages, this IE may not be included. To be reported by both MN and SN.
    globalGNB-ID   GlobalGNB-ID OPTIONAL,
    -- This IE shall not be used. This IE is replaced with globalNG-RANNode-ID.
    ...,
    globalNG-RANNode-ID GlobalNGRANNodeID OPTIONAL,
    -- C-ifDCSetup: This IE shall be present in messages from E2 Node to NearRT-RIC if DC is established, whereas from NearRT-RIC to E2 Node messages, this IE may not be included. To be reported only by SN.
    cell-RNTI      Cell-RNTI OPTIONAL
}

UEID-GNB-CU-CP-E1AP-ID-List ::= SEQUENCE (SIZE (1..maxE1APid)) OF UEID-GNB-CU-CP-E1AP-ID-Item

UEID-GNB-CU-CP-E1AP-ID-Item ::= SEQUENCE {
    gNB-CU-CP-UE-E1AP-ID GNB-CU-CP-UE-E1AP-ID,
    ...
}

UEID-GNB-CU-F1AP-ID-List ::= SEQUENCE (SIZE (1..maxF1APid)) OF UEID-GNB-CU-CP-F1AP-ID-Item

UEID-GNB-CU-CP-F1AP-ID-Item ::= SEQUENCE {
    gNB-CU-UE-F1AP-ID GNB-CU-UE-F1AP-ID,
    ...
}

UEID-GNB-DU ::= SEQUENCE {
    gNB-CU-UE-F1AP-ID GNB-CU-UE-F1AP-ID,
    ran-UEID       RANUEID OPTIONAL,
    ...,
    cell-RNTI      Cell-RNTI OPTIONAL
}

UEID-GNB-CU-UP ::= SEQUENCE {
    gNB-CU-CP-UE-E1AP-ID GNB-CU-CP-UE-E1AP-ID,
    ran-UEID       RANUEID OPTIONAL,
    ...
}

UEID-NG-ENB ::= SEQUENCE {
    amf-UE-NGAP-ID AMF-UE-NGAP-ID,
    guami          GUAMI,
    ng-eNB-CU-UE-W1AP-ID NGENB-CU-UE-W1AP-ID OPTIONAL,
    -- C-ifCUDUseparated: This IE shall be present in messages from E2 Node to NearRT-RIC for a CU-DU separated ng-eNB, whereas from NearRT-RIC to E2 Node messages, this IE may not be included.
    m-NG-RAN-UE-XnAP-ID NG-RANnodeUEXnAPID OPTIONAL,
    -- C-ifDCSetup: This IE shall be present in messages from E2 Node to NearRT-RIC if DC is established, whereas from NearRT-RIC to E2 Node messages, this IE may not be included. To be reported by both MN and SN.
    globalNgENB-ID GlobalNgENB-ID OPTIONAL,
    -- This IE shall not be used. This IE is replaced with globalNG-RANNode-ID.
    ...,
    globalNG-RANNode-ID GlobalNGRANNodeID OPTIONAL,
    -- C-ifDCSetup: This IE shall be present in messages from E2 Node to NearRT-RIC if DC is established, whereas from NearRT-RIC to E2 Node messages, this IE may not be included. To be reported only by SN.
    cell-RNTI      Cell-RNTI OPTIONAL
}

UEID-NG-ENB-DU ::= SEQUENCE {
    ng-eNB-CU-UE-W1AP-ID NGENB-CU-UE-W1AP-ID,
    ...,
    cell-RNTI      Cell-RNTI OPTIONAL
}

UEID-EN-GNB ::= SEQUENCE {
    m-eNB-UE-X2AP-ID ENB-UE-X2AP-ID,
    m-eNB-UE-X2AP-ID-Extension ENB-UE-X2AP-ID-Extension OPTIONAL,
    globalENB-ID   GlobalENB-ID,
    gNB-CU-UE-F1AP-ID GNB-CU-UE-F1AP-ID OPTIONAL,
    -- C-ifCUDUseparated: This IE shall be present in messages from E2 Node to NearRT-RIC for a CU-DU separated en-gNB, whereas from NearRT-RIC to E2 Node messages, this IE may not be included.
    gNB-CU-CP-UE-E1AP-ID-List UEID-GNB-CU-CP-E1AP-ID-List OPTIONAL,
    -- C-ifCPUPseparated: This IE shall be present in messages from E2 Node to NearRT-RIC for a CP-UP separated en-gNB, whereas from NearRT-RIC to E2 Node messages, this IE may not be included.
    ran-UEID       RANUEID OPTIONAL,
    ...,
    cell-RNTI      Cell-RNTI OPTIONAL
}

UEID-ENB ::= SEQUENCE {
    mME-UE-S1AP-ID MME-UE-S1AP-ID,
    gUMMEI         GUMMEI,
    m-eNB-UE-X2AP-ID ENB-UE-X2AP-ID OPTIONAL,
    -- This IE shall be present in messages from E2 Node to NearRT-RIC if DC is established, whereas from NearRT-RIC to  E2 Node messages, this IE may not be included.To be reported by MeNB and SeNB.
    m-eNB-UE-X2AP-ID-Extension ENB-UE-X2AP-ID-Extension OPTIONAL,
    globalENB-ID   GlobalENB-ID OPTIONAL,
    -- This IE shall be present in messages from E2 Node to NearRT-RIC if DC is established, whereas from NearRT-RIC to E2 Node messages, this IE may not be included.To be reported only by SeNB.
    ...,
    cell-RNTI      Cell-RNTI OPTIONAL
}

-- **************************************************************
-- 3GPP derived IEs
-- **************************************************************
-- NOTE:
-- - Extension fields removed and replaced with "..."
-- - IE names modified across all extracts to use "PLMNIdentity"
-- **************************************************************
-- IEs derived from 3GPP 36.413 (S1AP)
-- **************************************************************
-- **************************************************************
ENB-ID ::= CHOICE {
    macro-eNB-ID   BIT STRING (SIZE (20)),
    home-eNB-ID    BIT STRING (SIZE (28)),
    ...,
    short-Macro-eNB-ID BIT STRING (SIZE (18)),
    long-Macro-eNB-ID BIT STRING (SIZE (21))
}

GlobalENB-ID ::= SEQUENCE {
    pLMNIdentity   PLMNIdentity,
    eNB-ID         ENB-ID,
    ...
}

GUMMEI ::= SEQUENCE {
    pLMN-Identity  PLMNIdentity,
    mME-Group-ID   MME-Group-ID,
    mME-Code       MME-Code,
    ...
}

MME-Group-ID ::= OCTET STRING (SIZE (2))

MME-Code ::= OCTET STRING (SIZE (1))

MME-UE-S1AP-ID ::= INTEGER (0..4294967295)

QCI ::= INTEGER (0..255)

SubscriberProfileIDforRFP ::= INTEGER (1..256)

-- **************************************************************
-- IEs derived from 3GPP 36.423 (X2AP)
-- **************************************************************
-- Extension fields removed.
-- Note: to avoid duplicate names with NGAP, XnAP, etc.:
-- GNB-ID renamed ENGNB-ID,
-- GlobalGNB-ID renamed GlobalenGNB-ID,
-- UE-X2AP-ID renamed ENB-UE-X2AP-ID
-- UE-X2AP-ID-Extension renamed ENB-UE-X2AP-ID-Extension
-- **************************************************************
EN-GNB-ID ::= CHOICE {
    en-gNB-ID      BIT STRING (SIZE (22..32)),
    ...
}

ENB-UE-X2AP-ID ::= INTEGER (0..4095)

ENB-UE-X2AP-ID-Extension ::= INTEGER (0..4095, ...)

E-UTRA-ARFCN ::= INTEGER (0..maxEARFCN)

E-UTRA-PCI ::= INTEGER (0..503, ...)

E-UTRA-TAC ::= OCTET STRING (SIZE (2))

GlobalenGNB-ID ::= SEQUENCE {
    pLMN-Identity  PLMNIdentity,
    en-gNB-ID      EN-GNB-ID,
    ...
}

-- **************************************************************
-- IEs derived from 3GPP 37.473 (W1AP)
-- **************************************************************
NGENB-CU-UE-W1AP-ID ::= INTEGER (0..4294967295)

NGENB-DU-ID ::= INTEGER (0..68719476735)

-- **************************************************************
-- IEs derived from 3GPP 38.331 (NR RRC)
-- **************************************************************
NR-SSB-Index ::= INTEGER (0..maxNrofSSBs-1)

RNTI-Value ::= INTEGER (0..65535)

-- **************************************************************
-- IEs derived from 3GPP 38.413 (NGAP)
-- Extension fields removed and replaced with ...
-- **************************************************************
AMFPointer ::= BIT STRING (SIZE (6))

AMFRegionID ::= BIT STRING (SIZE (8))

AMFSetID ::= BIT STRING (SIZE (10))

AMF-UE-NGAP-ID ::= INTEGER (0..1099511627775)

EUTRACellIdentity ::= BIT STRING (SIZE (28))

EUTRA-CGI ::= SEQUENCE {
    pLMNIdentity   PLMNIdentity,
    eUTRACellIdentity EUTRACellIdentity,
    ...
}

FiveQI ::= INTEGER (0..255, ...)

GlobalGNB-ID ::= SEQUENCE {
    pLMNIdentity   PLMNIdentity,
    gNB-ID         GNB-ID,
    ...
}

GlobalNgENB-ID ::= SEQUENCE {
    pLMNIdentity   PLMNIdentity,
    ngENB-ID       NgENB-ID,
    ...
}

GNB-ID ::= CHOICE {
    gNB-ID         BIT STRING (SIZE (22..32)),
    ...
}

GUAMI ::= SEQUENCE {
    pLMNIdentity   PLMNIdentity,
    aMFRegionID    AMFRegionID,
    aMFSetID       AMFSetID,
    aMFPointer     AMFPointer,
    ...
}

IndexToRFSP ::= INTEGER (1..256, ...)

NgENB-ID ::= CHOICE {
    macroNgENB-ID  BIT STRING (SIZE (20)),
    shortMacroNgENB-ID BIT STRING (SIZE (18)),
    longMacroNgENB-ID BIT STRING (SIZE (21)),
    ...
}

NRCellIdentity ::= BIT STRING (SIZE (36))

NR-CGI ::= SEQUENCE {
    pLMNIdentity   PLMNIdentity,
    nRCellIdentity NRCellIdentity,
    ...
}

PLMNIdentity ::= OCTET STRING (SIZE (3))

QosFlowIdentifier ::= INTEGER (0..63, ...)

SD ::= OCTET STRING (SIZE (3))

S-NSSAI ::= SEQUENCE {
    sST            SST,
    sD             SD OPTIONAL,
    ...
}

SST ::= OCTET STRING (SIZE (1))

-- **************************************************************
-- IEs derived from 3GPP 38.423 (XnAP)
-- **************************************************************
NG-RANnodeUEXnAPID ::= INTEGER (0..4294967295)

GlobalNGRANNodeID ::= CHOICE {
    gNB            GlobalGNB-ID,
    ng-eNB         GlobalNgENB-ID,
    ...
}

-- **************************************************************
-- IEs derived from 3GPP 37.483 (E1AP)
-- **************************************************************
GNB-CU-CP-UE-E1AP-ID ::= INTEGER (0..4294967295)

GNB-CU-UP-ID ::= INTEGER (0..68719476735)

-- **************************************************************
-- IEs derived from 3GPP 38.473 (F1AP)
-- **************************************************************
FiveGS-TAC ::= OCTET STRING (SIZE (3))

FreqBandNrItem ::= SEQUENCE {
    freqBandIndicatorNr INTEGER (1..1024, ...),
    ...
}

GNB-CU-UE-F1AP-ID ::= INTEGER (0..4294967295)

GNB-DU-ID ::= INTEGER (0..68719476735)

NR-PCI ::= INTEGER (0..1007)

NR-ARFCN ::= SEQUENCE {
    nRARFCN        INTEGER (0..maxNRARFCN),
    ...
}

NRFrequencyBand-List ::= SEQUENCE (SIZE (1..maxnoofNrCellBands)) OF NRFrequencyBandItem

NRFrequencyBandItem ::= SEQUENCE {
    freqBandIndicatorNr INTEGER (1..1024, ...),
    supportedSULBandList SupportedSULBandList,
    ...
}

NRFrequencyInfo ::= SEQUENCE {
    nrARFCN        NR-ARFCN,
    frequencyBand-List NRFrequencyBand-List,
    frequencyShift7p5khz NRFrequencyShift7p5khz OPTIONAL,
    ...
}

NRFrequencyShift7p5khz ::= ENUMERATED {
                   false,
                   true,
                   ...
               }

RANUEID ::= OCTET STRING (SIZE (8))

SupportedSULBandList ::= SEQUENCE (SIZE (0..maxnoofNrCellBands)) OF SupportedSULFreqBandItem

SupportedSULFreqBandItem ::= SEQUENCE {
    freqBandIndicatorNr INTEGER (1..1024, ...),
    ...
}

END

     -- ASN1STOP
